ChallengeString ::= OCTET STRING(SIZE (8..128))

TimeStamp ::= INTEGER(1..4294967295) -- seconds since 00:00 
                     

-- 1/1/1970 UTC
RandomVal ::= INTEGER -- 32-bit Integer

Password ::= BMPString(SIZE (1..128))

Identifier ::= BMPString(SIZE (1..128))

KeyMaterial ::= BIT STRING(SIZE (1..2048))

IV8 ::= OCTET STRING(SIZE (8)) -- initial value for 64-bit block ciphers
                    

IV16 ::= OCTET STRING(SIZE (16)) -- initial value for 128-bit block ciphers

ECpoint ::= SEQUENCE
{
  x  BIT STRING(SIZE (0..511)) OPTIONAL,
  y  BIT STRING(SIZE (0..511)) OPTIONAL,
  ...
}

Params ::= SEQUENCE
{
  ranInt        INTEGER OPTIONAL, -- some integer value
  iv8           IV8 OPTIONAL, -- 8 octet initialization vector
  ...,
  iv16          IV16 OPTIONAL, -- 16 octet initialization vector
  iv            OCTET STRING OPTIONAL, -- arbitrary length initialization vector
  clearSalt     OCTET STRING OPTIONAL -- unencrypted salting key for [TSB51]encryption
}

KeySyncMaterial ::= SEQUENCE
{
  generalID    Identifier,
  keyMaterial  KeyMaterial,
  ...
}

EncodedKeySyncMaterial ::= TYPE-IDENTIFIER.&Type(KeySyncMaterial)


V3KeySyncMaterial ::= SEQUENCE
{
  generalID            Identifier OPTIONAL, -- peer terminal ID
  algorithmOID         OBJECT IDENTIFIER OPTIONAL, -- encryption algorithm
  paramS               Params, -- IV
  encryptedSessionKey  OCTET STRING OPTIONAL, -- encrypted session key
  encryptedSaltingKey  OCTET STRING OPTIONAL, -- encrypted media salting 
  
  -- key
  clearSaltingKey      OCTET STRING OPTIONAL, -- unencrypted media salting 
  
  -- key
  paramSsalt           Params OPTIONAL, -- IV (and clear salt) for salting 
  
  -- key encryption
  keyDerivationOID     OBJECT IDENTIFIER OPTIONAL, -- key derivation 
  
  -- method
  ...
}

EncryptedEncodedKeySyncMaterial::= SEQUENCE
{
  algorithmOID   OBJECT IDENTIFIER,
  paramS         Params, -- any "runtime" parameters
  encryptedData  OCTET STRING
}

KeySignedMaterial ::= SEQUENCE
{
  generalId  Identifier, -- slave's alias
  mrandom    RandomVal, -- master's random value
  srandom    RandomVal OPTIONAL, -- slave's random value
  timeStamp  TimeStamp OPTIONAL, -- master's timestamp for unsolicited EU
  encrptval  EncryptedEncodedKeySyncMaterial
}

EncodedKeySignedMaterial ::= TYPE-IDENTIFIER.&Type(KeySignedMaterial)

SignedEncodedKeySignedMaterial::= SEQUENCE
{
  toBeSigned    EncodedKeySignedMaterial,
  algorithmOID  OBJECT IDENTIFIER,
  paramS        Params, -- any "runtime" parameters
  signature     BIT STRING -- could be an RSA or an ASN.1 coded ECGDSASignature
}

H235Key ::= CHOICE -- This is used with the H.245 or ClearToken "h235Key" field
{
  secureChannel       KeyMaterial,
  sharedSecret        EncryptedEncodedKeySyncMaterial,
  certProtectedKey    SignedEncodedKeySignedMaterial,
  ...,
  secureSharedSecret  V3KeySyncMaterial -- for H.235 V3 end points
}
